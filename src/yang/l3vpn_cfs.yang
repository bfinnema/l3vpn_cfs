module l3vpn_cfs {

  namespace "http://example.com/l3vpn_cfs";
  prefix l3vpn_cfs;

  import ietf-inet-types {
    prefix inet;
  }
  import tailf-common {
    prefix tailf;
  }
  import tailf-ncs {
    prefix ncs;
  }

  description
    "L3VPN CFS";

  revision 2024-07-02 {
    description
      "Initial revision.";
  }

  grouping interface_grouping {
    leaf interface_name {
      tailf:info "Interface name. For example TenGigE.";
      type enumeration {
        enum FastEthernet;
        enum GigabitEthernet;
        enum TenGigE;
        enum TwentyFiveGigE;
        enum FortyGigE;
        enum FiftyGigE;
        enum HundredGigE;
        enum TwoHundredGigE;
        enum FourHundredGigE;
        enum EightHundredGigE;
        enum xe;
      }
    }
    leaf interface_number {
      tailf:info "Interface number. For example 0 or 1/0";
      type string {
        pattern "[0-9]{1,2}(/[0-9]{1,2}){1,4}";
      }
    }
    leaf ipv4_address {
      tailf:info "Interface IPv4 address.";
      type inet:ipv4-address;
    }
    leaf ipv4_mask {
      tailf:info "Interface IPv4 mask.";
      type inet:ipv4-address;
    }
    leaf interface_description {
      tailf:info "Interface description.";
      type string;
    }
  }

  list l3vpn_cfs {
    description "This is an RFS skeleton service";

    key vrf_name;
    leaf vrf_name {
      tailf:info "Unique name of the VRF";
      tailf:cli-allow-range;
      type string;
    }

    uses ncs:service-data;
    ncs:servicepoint l3vpn_cfs-servicepoint;

    leaf as_number {
      tailf:info "SP Autonomous System number eg 65000";
      type uint16;
      mandatory true;
    }

    leaf customer_as_number {
      tailf:info "Remote Autonomous System number of the customer eg 65002";
      type uint16;
      mandatory true;
    }

    list endpoint {
      key id;
      leaf id {
        tailf:info "Endpoint identifier. It should be the id of the CPE. It will be added to the hostname";
        type string;
      }

      leaf pe_device {
        type leafref {
          path "/ncs:devices/ncs:device/ncs:name";
        }
      }

      leaf cpe_device {
        type leafref {
          path "/ncs:devices/ncs:device/ncs:name";
        }
      }

      leaf cpe_loopback0_address {
        tailf:info "Address of the Loopback 0 interface of the CPE. The mask is assumed to be /32";
        type inet:ipv4-address;
      }

      container pe_interface {
        uses interface_grouping;
      }

      container cpe_interface {
        uses interface_grouping;
      }
    }
  }
}
